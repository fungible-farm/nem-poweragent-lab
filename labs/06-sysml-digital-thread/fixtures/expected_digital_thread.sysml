package DigitalThread {
    // Generated by labs/06-sysml-digital-thread/generate_sysml.py -- do not hand-edit.
    // Source: labs/06-sysml-digital-thread/schema/digital_thread_instances.yaml

    part def Agent {
        attribute source : String;
        attribute uses : String;
        attribute refreshCadence : String;
        attribute owner : String;
    }

    part def MCPServer {
        attribute source : String;
        attribute refreshCadence : String;
        attribute owner : String;
    }

    part def DataSource {
        attribute source : String;
        attribute refreshCadence : String;
        attribute owner : String;
    }

    part digitalThread {
        part lab1_bisection_search : Agent {
            attribute source = "labs/01-simple-loadflow-fit/run.py";
            attribute uses = "csiro_synthetic_nem_2000bus";
            attribute refreshCadence = "on every lab run (--step fit)";
            attribute owner = "Lab 1 -- load-flow parameter fit";
        }

        part lab3_local_policy_search : Agent {
            attribute source = "labs/03-advanced-provider-bakeoff/orchestrator.py";
            attribute uses = "csiro_synthetic_nem_2000bus";
            attribute refreshCadence = "on every --step sweep";
            attribute owner = "Lab 3 -- multi-provider bake-off (local-policy-A/B/C)";
        }

        part powermcp_pandapower : MCPServer {
            attribute source = "kube/powermcp-pandapower-pod.yaml";
            attribute refreshCadence = "on-demand, podman kube play";
            attribute owner = "root README \"Connecting to the MCP servers\"";
        }

        part codebase_memory : MCPServer {
            attribute source = ".mcp.json";
            attribute refreshCadence = "always-on, registered MCP server";
            attribute owner = "repo tooling (codebase-memory-mcp)";
        }

        part csiro_synthetic_nem_2000bus : DataSource {
            attribute source = "scripts/fetch_csiro_nem_data.py";
            attribute refreshCadence = "static case file, fetched once and checksum-verified";
            attribute owner = "Labs 1, 2, 4, 6";
        }

        part aemo_nemweb_nemosis : DataSource {
            attribute source = "labs/04-aemo-digital-twin-reconciliation/fetch_day.py";
            attribute refreshCadence = "pulled per requested date via NEMOSIS";
            attribute owner = "Lab 4 -- digital-twin reconciliation";
        }

        part simbench_1_mv_rural : DataSource {
            attribute source = "labs/05-spartan-chaosnet-transient-stream/chaosnet.py";
            attribute refreshCadence = "static seed grid, perturbed per run (Watts-Strogatz)";
            attribute owner = "Lab 5 -- SPARTAN chaos-net";
        }
    }
}
