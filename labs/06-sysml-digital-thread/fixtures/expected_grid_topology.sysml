package GridTopology {
    // Generated by labs/06-sysml-digital-thread/generate_sysml.py -- do not hand-edit.
    // Source: labs/06-sysml-digital-thread/schema/grid_instances.yaml

    part def Bus {
        attribute source : String;
        attribute voltageKV : Real;
    }

    part def Generator {
        attribute source : String;
        attribute bus : String;
        attribute ratedMW : Real;
    }

    part def Line {
        attribute source : String;
        attribute fromBus : String;
        attribute toBus : String;
        attribute kind : String;
        attribute lengthKM : Real;
    }

    part gridTopology {
        part bus_4052 : Bus {
            attribute source = "data/snemSA.m (pandapower bus index 1683)";
            attribute voltageKV = 15.75;
        }

        part bus_4128 : Bus {
            attribute source = "data/snemSA.m (pandapower bus index 1744)";
            attribute voltageKV = 275.0;
        }

        part bus_4125 : Bus {
            attribute source = "data/snemSA.m (pandapower bus index 1741)";
            attribute voltageKV = 275.0;
        }

        part bus_4148 : Bus {
            attribute source = "data/snemSA.m (pandapower bus index 1763)";
            attribute voltageKV = 275.0;
        }

        part bus_4053 : Bus {
            attribute source = "data/snemSA.m (pandapower bus index 1684)";
            attribute voltageKV = 15.75;
        }

        part bus_4054 : Bus {
            attribute source = "data/snemSA.m (pandapower bus index 1685)";
            attribute voltageKV = 15.75;
        }

        part bus_4124 : Bus {
            attribute source = "data/snemSA.m (pandapower bus index 1740)";
            attribute voltageKV = 275.0;
        }

        part bus_4238 : Bus {
            attribute source = "data/snemSA.m (pandapower bus index 1852)";
            attribute voltageKV = 66.0;
        }

        part bus_4129 : Bus {
            attribute source = "data/snemSA.m (pandapower bus index 1745)";
            attribute voltageKV = 275.0;
        }

        part bus_4335 : Bus {
            attribute source = "data/snemSA.m (pandapower bus index 1945)";
            attribute voltageKV = 66.0;
        }

        part bus_4094 : Bus {
            attribute source = "data/snemSA.m (pandapower bus index 1714)";
            attribute voltageKV = 275.0;
        }

        part bus_4095 : Bus {
            attribute source = "data/snemSA.m (pandapower bus index 1715)";
            attribute voltageKV = 275.0;
        }

        part bus_4112 : Bus {
            attribute source = "data/snemSA.m (pandapower bus index 1728)";
            attribute voltageKV = 275.0;
        }

        part bus_4117 : Bus {
            attribute source = "data/snemSA.m (pandapower bus index 1733)";
            attribute voltageKV = 275.0;
        }

        part bus_4131 : Bus {
            attribute source = "data/snemSA.m (pandapower bus index 1746)";
            attribute voltageKV = 275.0;
        }

        part gen_4052 : Generator {
            attribute source = "data/snemSA.m (pandapower gen table, bus 1683)";
            attribute bus = "bus_4052";
            attribute ratedMW = 127.3;
        }

        part gen_4053 : Generator {
            attribute source = "data/snemSA.m (pandapower gen table, bus 1684)";
            attribute bus = "bus_4053";
            attribute ratedMW = 135.2;
        }

        part gen_4054 : Generator {
            attribute source = "data/snemSA.m (pandapower gen table, bus 1685)";
            attribute bus = "bus_4054";
            attribute ratedMW = 137.6;
        }

        part gen_4094 : Generator {
            attribute source = "data/snemSA.m (pandapower gen table, bus 1714)";
            attribute bus = "bus_4094";
            attribute ratedMW = 0.0;
        }

        part gen_4095 : Generator {
            attribute source = "data/snemSA.m (pandapower gen table, bus 1715)";
            attribute bus = "bus_4095";
            attribute ratedMW = 0.0;
        }

        part line_4117_4124 : Line {
            attribute source = "data/snemSA.m (pandapower line table, 1733-1740)";
            attribute fromBus = "bus_4117";
            attribute toBus = "bus_4124";
            attribute kind = "transmission";
            attribute lengthKM = 1.0;
        }

        part line_4117_4131 : Line {
            attribute source = "data/snemSA.m (pandapower line table, 1733-1746)";
            attribute fromBus = "bus_4117";
            attribute toBus = "bus_4131";
            attribute kind = "transmission";
            attribute lengthKM = 1.0;
        }

        part line_4124_4131 : Line {
            attribute source = "data/snemSA.m (pandapower line table, 1740-1746)";
            attribute fromBus = "bus_4124";
            attribute toBus = "bus_4131";
            attribute kind = "transmission";
            attribute lengthKM = 1.0;
        }

        part line_4094_4124 : Line {
            attribute source = "data/snemSA.m (pandapower line table, 1714-1740)";
            attribute fromBus = "bus_4094";
            attribute toBus = "bus_4124";
            attribute kind = "transmission";
            attribute lengthKM = 1.0;
        }

        part line_4095_4124 : Line {
            attribute source = "data/snemSA.m (pandapower line table, 1715-1740)";
            attribute fromBus = "bus_4095";
            attribute toBus = "bus_4124";
            attribute kind = "transmission";
            attribute lengthKM = 1.0;
        }

        part line_4112_4129 : Line {
            attribute source = "data/snemSA.m (pandapower line table, 1728-1745)";
            attribute fromBus = "bus_4112";
            attribute toBus = "bus_4129";
            attribute kind = "transmission";
            attribute lengthKM = 1.0;
        }

        part line_4112_4129_2 : Line {
            attribute source = "data/snemSA.m (pandapower line table, 1728-1745)";
            attribute fromBus = "bus_4112";
            attribute toBus = "bus_4129";
            attribute kind = "transmission";
            attribute lengthKM = 1.0;
        }

        part line_4129_4148 : Line {
            attribute source = "data/snemSA.m (pandapower line table, 1745-1763)";
            attribute fromBus = "bus_4129";
            attribute toBus = "bus_4148";
            attribute kind = "transmission";
            attribute lengthKM = 1.0;
        }

        part line_4112_4124 : Line {
            attribute source = "data/snemSA.m (pandapower line table, 1728-1740)";
            attribute fromBus = "bus_4112";
            attribute toBus = "bus_4124";
            attribute kind = "transmission";
            attribute lengthKM = 1.0;
        }

        part line_4124_4125 : Line {
            attribute source = "data/snemSA.m (pandapower line table, 1740-1741)";
            attribute fromBus = "bus_4124";
            attribute toBus = "bus_4125";
            attribute kind = "transmission";
            attribute lengthKM = 1.0;
        }

        part line_4125_4128 : Line {
            attribute source = "data/snemSA.m (pandapower line table, 1741-1744)";
            attribute fromBus = "bus_4125";
            attribute toBus = "bus_4128";
            attribute kind = "transmission";
            attribute lengthKM = 1.0;
        }

        part line_4128_4148 : Line {
            attribute source = "data/snemSA.m (pandapower line table, 1744-1763)";
            attribute fromBus = "bus_4128";
            attribute toBus = "bus_4148";
            attribute kind = "transmission";
            attribute lengthKM = 1.0;
        }

        part xfmr_4125_4238 : Line {
            attribute source = "data/snemSA.m (pandapower trafo table, 1741-1852)";
            attribute fromBus = "bus_4125";
            attribute toBus = "bus_4238";
            attribute kind = "transformer";
        }

        part xfmr_4125_4238_2 : Line {
            attribute source = "data/snemSA.m (pandapower trafo table, 1741-1852)";
            attribute fromBus = "bus_4125";
            attribute toBus = "bus_4238";
            attribute kind = "transformer";
        }

        part xfmr_4128_4052 : Line {
            attribute source = "data/snemSA.m (pandapower trafo table, 1744-1683)";
            attribute fromBus = "bus_4128";
            attribute toBus = "bus_4052";
            attribute kind = "transformer";
        }

        part xfmr_4128_4053 : Line {
            attribute source = "data/snemSA.m (pandapower trafo table, 1744-1684)";
            attribute fromBus = "bus_4128";
            attribute toBus = "bus_4053";
            attribute kind = "transformer";
        }

        part xfmr_4128_4054 : Line {
            attribute source = "data/snemSA.m (pandapower trafo table, 1744-1685)";
            attribute fromBus = "bus_4128";
            attribute toBus = "bus_4054";
            attribute kind = "transformer";
        }

        part xfmr_4148_4335 : Line {
            attribute source = "data/snemSA.m (pandapower trafo table, 1763-1945)";
            attribute fromBus = "bus_4148";
            attribute toBus = "bus_4335";
            attribute kind = "transformer";
        }

        part xfmr_4148_4335_2 : Line {
            attribute source = "data/snemSA.m (pandapower trafo table, 1763-1945)";
            attribute fromBus = "bus_4148";
            attribute toBus = "bus_4335";
            attribute kind = "transformer";
        }
    }
}
