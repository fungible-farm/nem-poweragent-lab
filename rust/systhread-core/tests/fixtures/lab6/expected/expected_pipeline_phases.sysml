package PipelinePhases {
    // Generated by labs/06-sysml-digital-thread/generate_sysml.py -- do not hand-edit.
    // Source: labs/06-sysml-digital-thread/schema/pipeline_phases_instances.yaml

    part def Phase {
        attribute source : String;
        attribute role : String;
        attribute next : String;
    }

    part pipelinePhases {
        part phase0_source_location : Phase {
            attribute source = "docs/prd/0005-grid-forming-stabilizer-and-renewable-models.md";
            attribute role = "Locate the real public IEC 61400-27-1 Type 4 Modelica source before Phase 4 depends on it -- resolved: it lives in RTE's own dynawo/dynawo GitHub repository (MPL-2.0), not a standalone repo. A research finding, not a script -- source above is the PRD's own \"Open questions\" section recording that resolution.";
            attribute next = "phase1_grid_forming";
        }

        part phase1_grid_forming : Phase {
            attribute source = "labs/05-spartan-chaosnet-transient-stream/grid_forming.py";
            attribute role = "Build a VSM-style grid-forming stabilizer against Lab 5's real chaos_schedule.yaml fault and measure a real before/after mitigation number from an actual DPsim run.";
            attribute next = "phase1_5_headroom_translation";
        }

        part phase1_5_headroom_translation : Phase {
            attribute source = "labs/05-spartan-chaosnet-transient-stream/headroom_translation.py";
            attribute role = "Translate Phase 1's real EMT-domain mitigation into an OPF constraint-headroom question against the same fault-adjacent line, and report whether any binding constraint actually changes -- turning \"the stabilizer works\" into \"the stabilizer is operationally meaningful.\"";
            attribute next = "phase2_delay_compensation";
        }

        part phase2_delay_compensation : Phase {
            attribute source = "labs/05-spartan-chaosnet-transient-stream/delay_compensation.py";
            attribute role = "Add a deadtime/Smith-predictor cable-length delay-compensation term to Phase 1's controller and report, with a real comparison, whether it measurably helps versus Phase 1's baseline.";
        }
    }
}
